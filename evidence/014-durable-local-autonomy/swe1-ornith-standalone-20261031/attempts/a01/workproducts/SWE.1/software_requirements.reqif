# SWE.1 Software Requirements
Generated deterministically by Forge-C from workproducts/SWE.1/software_requirements.md (sha256 96bac35f5e4cf737); EARS markdown is the source of truth.

# Specification: SWE.1 Software Requirements

## SWR-001 (Software Requirement)
When the caller invokes LL_CRC_Write_IDR with a valid CRC peripheral instance, the CRC LL driver shall write the supplied 32-bit value to the IDR field of CRC_IDR.
- EARS pattern: EVENT
- Source: RM0486 p.1172
- verified-by -> R18

## SWR-002 (Software Requirement)
While the caller invokes LL_CRC_Read_IDR with a valid CRC peripheral instance, the CRC LL driver shall read the CRC_IDR register and return the current 32-bit value stored in the IDR field of CRC_IDR.
- EARS pattern: STATE
- Source: RM0486 p.1172
- verified-by -> R19

## SWR-003 (Software Requirement)
While no LL function has been called after reset, the CRC LL driver shall not write any register.
- EARS pattern: STATE
- Source: RM0486 p.1170
- verified-by -> R12

## SWR-004 (Software Requirement)
When the caller invokes LL_CRC_Read_IDR with a valid CRC peripheral instance, the CRC LL driver shall not wait on any status flag of the CRC peripheral.
- EARS pattern: EVENT
- Source: RM0486 p.1170
- verified-by -> R20

## SWR-005 (Software Requirement)
When the caller invokes LL_CRC_Read_IDR with a valid CRC peripheral instance, the CRC LL driver shall not return an error code for the valid accessible call.
- EARS pattern: EVENT
- Source: RM0486 p.1170
- verified-by -> R21

## SWR-006 (Software Requirement)
When the caller invokes LL_CRC_Write_IDR with a valid CRC peripheral instance, the CRC LL driver shall change only the IDR field of CRC_IDR and no other field of the register.
- EARS pattern: EVENT
- Source: RM0486 p.1170
- verified-by -> R22

## SWR-007 (Software Requirement)
The CRC LL driver shall occupy at most 4096 bytes of flash.
- EARS pattern: UBIQUITOUS
- Source: work-order budget (owner development target)
- verified-by -> R13

## SWR-008 (Software Requirement)
The CRC LL driver shall use at most 64 bytes of static RAM.
- EARS pattern: UBIQUITOUS
- Source: work-order budget (owner development target)
- verified-by -> R14

## SWR-009 (Software Requirement)
The CRC LL driver shall use at most 128 bytes of stack for any public API call.
- EARS pattern: UBIQUITOUS
- Source: work-order budget (owner development target)
- verified-by -> R15

## SWR-010 (Software Requirement)
When a scoped API is measured in the pinned Renode profile at 100 MIPS without injected interrupts or bus stalls, the CRC LL driver shall complete each measured call within 64 executed target instructions.
- EARS pattern: EVENT
- Source: work-order simulation-only performance allocation; not a reference-manual or silicon timing claim
- verified-by -> R16

## SWR-011 (Software Requirement)
When a scoped API is measured in the pinned Renode profile at 100 MIPS without injected interrupts or bus stalls, the CRC LL driver shall complete each measured call within 100 microseconds of virtual time.
- EARS pattern: EVENT
- Source: work-order simulation-only performance allocation; not a reference-manual or silicon timing claim
- verified-by -> R17

## R12: SWR-003 (Verification Test)

## R13: SWR-007 (Verification Test)

## R14: SWR-008 (Verification Test)

## R15: SWR-009 (Verification Test)

## R16: SWR-010 (Verification Test)

## R17: SWR-011 (Verification Test)

## R18: UT-001 (Verification Test)

## R19: UT-002 (Verification Test)

## R20: UT-003 (Verification Test)

## R21: UT-004 (Verification Test)

## R22: UT-005 (Verification Test)
