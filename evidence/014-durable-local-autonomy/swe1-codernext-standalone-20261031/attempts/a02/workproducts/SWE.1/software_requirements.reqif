# SWE.1 Software Requirements
Generated deterministically by Forge-C from workproducts/SWE.1/software_requirements.md (sha256 9b4649e05b78a910); EARS markdown is the source of truth.

# Specification: SWE.1 Software Requirements

## SWR-001 (Software Requirement)
The CRC LL driver shall write the 32-bit value provided by the caller into the CRC_IDR.IDR register when LL_CRC_Write_IDR is invoked with a valid CRC peripheral instance and the register interface is accessible.
- EARS pattern: UBIQUITOUS
- Source: RM0486 p.1172
- verified-by -> R15

## SWR-002 (Software Requirement)
The CRC LL driver shall return the current 32-bit value stored in the CRC_IDR.IDR register when LL_CRC_Read_IDR is invoked with a valid CRC peripheral instance and the register interface is accessible.
- EARS pattern: UBIQUITOUS
- Source: RM0486 p.1172
- verified-by -> R16

## SWR-003 (Software Requirement)
While no LL function has been called after reset, the CRC LL driver shall not write any register.
- EARS pattern: STATE
- Source: RM0486 p.1170
- verified-by -> R9

## SWR-004 (Software Requirement)
The CRC LL driver shall occupy at most 4096 bytes of flash.
- EARS pattern: UBIQUITOUS
- Source: work-order budget (owner development target)
- verified-by -> R10

## SWR-005 (Software Requirement)
The CRC LL driver shall use at most 64 bytes of static RAM.
- EARS pattern: UBIQUITOUS
- Source: work-order budget (owner development target)
- verified-by -> R11

## SWR-006 (Software Requirement)
The CRC LL driver shall use at most 128 bytes of stack for any public API call.
- EARS pattern: UBIQUITOUS
- Source: work-order budget (owner development target)
- verified-by -> R12

## SWR-007 (Software Requirement)
When a scoped API is measured in the pinned Renode profile at 100 MIPS without injected interrupts or bus stalls, the CRC LL driver shall complete each measured call within 64 executed target instructions.
- EARS pattern: EVENT
- Source: work-order simulation-only performance allocation; not a reference-manual or silicon timing claim
- verified-by -> R13

## SWR-008 (Software Requirement)
When a scoped API is measured in the pinned Renode profile at 100 MIPS without injected interrupts or bus stalls, the CRC LL driver shall complete each measured call within 100 microseconds of virtual time.
- EARS pattern: EVENT
- Source: work-order simulation-only performance allocation; not a reference-manual or silicon timing claim
- verified-by -> R14

## R9: SWR-003 (Verification Test)

## R10: SWR-004 (Verification Test)

## R11: SWR-005 (Verification Test)

## R12: SWR-006 (Verification Test)

## R13: SWR-007 (Verification Test)

## R14: SWR-008 (Verification Test)

## R15: UT-001 (Verification Test)

## R16: UT-002 (Verification Test)
